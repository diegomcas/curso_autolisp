(defun p_params_mal	(cont)
	(setq cnt "Hey, Ahora soy un texto")
	(princ "  -> cnt = ") (princ cnt) (princ "\n")
	(princ "  -> cont = ") (princ cont) (princ "\n")
	(princ)
)

(defun p_params_bien (cont / cnt)
	(setq cnt "Hey, Ahora soy un texto")
	(princ "  -> cnt = ") (princ cnt) (princ "\n")
	(princ "  -> cont = ") (princ cont) (princ "\n")
	(princ)
)

(defun c:exe_mal ()
	(setq cnt 1)
	(setq str "Hola")
	(setq str_len (strlen str))

	(while (< cnt str_len)
		(setq char (substr str cnt 1))
		(princ "char = ") (princ char) (princ "\n")
		(p_params_mal cnt)
		(setq cnt (1+ cnt))
	)
)

(
 defun c:exe_bien ( / cnt str str_len char)
	(setq cnt 1)
	(setq str "Hola")
	(setq str_len (strlen str))

	(while (< cnt str_len)
		(setq char (substr str cnt 1))
		(princ "char = ") (princ char) (princ "\n")
		(p_params_bien cnt)
		(setq cnt (1+ cnt))
	)
)
